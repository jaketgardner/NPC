UX80-MIB DEFINITIONS ::= BEGIN

IMPORTS
     enterprises, IpAddress               FROM RFC1155-SMI
     OBJECT-TYPE                         FROM RFC-1212
     TRAP-TYPE                             FROM RFC-1215;

smartTechULC OBJECT IDENTIFIER
        ::= { enterprises 29485}

smartTechProducts OBJECT IDENTIFIER
        ::= {smartTechULC 3}

smartTechEmbeddedProducts OBJECT IDENTIFIER
        ::= {smartTechProducts 2}

ux80 OBJECT IDENTIFIER 
        ::= { smartTechEmbeddedProducts 10 }

powerState OBJECT-TYPE
        SYNTAX  INTEGER { 
                        onState(1),
                        offState(2),
                        poweringOnState(3),
                        coolingState(4),
                        confirmOffState(5)
                        }
        ACCESS read-write
        STATUS  mandatory
        DESCRIPTION
                "Write to on/off to turn the projector on or off.  Cooling and powering status only for reads."
        ::= { ux80 1 }


video OBJECT IDENTIFIER 
        ::= { ux80 2 }

inputSource OBJECT-TYPE
        SYNTAX  INTEGER {
			hdmi1(1),
			vga1(2),
			hdmi2(3),
			hdmi3(4),
			vga2(5),
			composite1(6),
			hdmi4(7),
			hdmi5(8),
			vga3(9),
			composite2(10),
			next(11)
		}
        ACCESS read-write
        STATUS  mandatory
        DESCRIPTION
                "To display the current input source as well as
                switch between input sources. Set to the following
                to switch to the specified source:
				1: HDMI 1
				2: VGA 1
                3: HDMI 2
				4: HDMI 3
                5: VGA 2
				6: COMPOSITE 1
                7: HDMI 4
				8: HDMI 5
                9: VGA 3
				10: COMPOSITE 2
                11: Next"
        ::= { video 1 }

hdmi1 OBJECT IDENTIFIER 
        ::= { video 2 }

hdmi1DisplayMode OBJECT-TYPE
        SYNTAX  INTEGER {
                        brightRoom(1),
                        darkRoom(2),
                        sRGB(3),
                        user(4),
                        smartPresentation(5)  }
        ACCESS read-write
        STATUS  mandatory
        DESCRIPTION
                "Video Display Mode"
        DEFVAL { smartPresentation }
        ::= { hdmi1 1 }
hdmi1Brightness OBJECT-TYPE
        SYNTAX  INTEGER (0..100)
        ACCESS read-write
        STATUS  mandatory
        DESCRIPTION
                "Video Brightness."
        ::= { hdmi1 2 }
hdmi1Contrast OBJECT-TYPE
        SYNTAX  INTEGER (0..100)
        ACCESS read-write
        STATUS  mandatory
        DESCRIPTION
                "Video Contrast."
        ::= { hdmi1 3 }

hdmi1Whitepeaking OBJECT-TYPE
        SYNTAX  INTEGER (0..10)
        ACCESS read-write
        STATUS  mandatory
        DESCRIPTION
                "Video White Peaking"
        ::= { hdmi1 4 }
hdmi1Degamma OBJECT-TYPE
        SYNTAX  INTEGER (0..3)
        ACCESS read-write
        STATUS  mandatory
        DESCRIPTION
                "Video Degamma"
        ::= { hdmi1 5 }
hdmi1Red OBJECT-TYPE
        SYNTAX  INTEGER (0..100)
        ACCESS read-write
        STATUS  mandatory
        DESCRIPTION
                "Video Red"
        ::= { hdmi1 6 }
hdmi1Green OBJECT-TYPE
        SYNTAX  INTEGER (0..100)
        ACCESS read-write
        STATUS  mandatory
        DESCRIPTION
                "Video Green"
        ::= { hdmi1 7 }
hdmi1Blue OBJECT-TYPE
        SYNTAX  INTEGER (0..100)
        ACCESS read-write
        STATUS  mandatory
        DESCRIPTION
                "Video Blue"
        ::= { hdmi1 8 }
hdmi1Cyan OBJECT-TYPE
        SYNTAX  INTEGER (0..100)
        ACCESS read-write
        STATUS  mandatory
        DESCRIPTION
                "Video Cyan"
        ::= { hdmi1 9 }
hdmi1Magenta OBJECT-TYPE
        SYNTAX  INTEGER (0..100)
        ACCESS read-write
        STATUS  mandatory
        DESCRIPTION
                "Video Magenta"
        ::= { hdmi1 10 }
hdmi1Yellow OBJECT-TYPE
        SYNTAX  INTEGER (0..100)
        ACCESS read-write
        STATUS  mandatory
        DESCRIPTION
                "Video Yellow"
        ::= { hdmi1 11 }

vga1 OBJECT IDENTIFIER 
        ::= { video 3 }
vga1DisplayMode OBJECT-TYPE
        SYNTAX  INTEGER {
                        brightRoom(1),
                        darkRoom(2),
                        sRGB(3),
                        user(4),
                        smartPresentation(5) }
        ACCESS read-write
        STATUS  mandatory
        DESCRIPTION
                "Video Display Mode"
        DEFVAL { smartPresentation }
        ::= { vga1 1 }
vga1Brightness OBJECT-TYPE
        SYNTAX  INTEGER (0..100)
        ACCESS read-write
        STATUS  mandatory
        DESCRIPTION
                "Video Brightness."
        ::= { vga1 2 }
vga1Contrast OBJECT-TYPE
        SYNTAX  INTEGER (0..100)
        ACCESS read-write
        STATUS  mandatory
        DESCRIPTION
                "Video Contrast."
        ::= { vga1 3 }
vga1Frequency OBJECT-TYPE
        SYNTAX  INTEGER (-5..5)
        ACCESS read-write
        STATUS  mandatory
        DESCRIPTION
                "Video Frequency"
        ::= { vga1 4 }
vga1Tracking OBJECT-TYPE
        SYNTAX  INTEGER (0..63)
        ACCESS read-write
        STATUS  mandatory
        DESCRIPTION
                "Video Tracking"
        ::= { vga1 5 }
vga1WhitePeaking OBJECT-TYPE
        SYNTAX  INTEGER (0..10)
        ACCESS read-write
        STATUS  mandatory
        DESCRIPTION
                "Video White Peaking"
        ::= { vga1 6 }
vga1Degamma OBJECT-TYPE
        SYNTAX  INTEGER (0..3)
        ACCESS read-write
        STATUS  mandatory
        DESCRIPTION
                "Video Degamma"
        ::= { vga1 7 }
vga1Red OBJECT-TYPE
        SYNTAX  INTEGER (0..100)
        ACCESS read-write
        STATUS  mandatory
        DESCRIPTION
                "Video Red"
        ::= { vga1 8 }
vga1Green OBJECT-TYPE
        SYNTAX  INTEGER (0..100)
        ACCESS read-write
        STATUS  mandatory
        DESCRIPTION
                "Video Green"
        ::= { vga1 9 }
vga1Blue OBJECT-TYPE
        SYNTAX  INTEGER (0..100)
        ACCESS read-write
        STATUS  mandatory
        DESCRIPTION
                "Video Blue"
        ::= { vga1 10 }
vga1Cyan OBJECT-TYPE
        SYNTAX  INTEGER (0..100)
        ACCESS read-write
        STATUS  mandatory
        DESCRIPTION
                "Video Cyan"
        ::= { vga1 11 }
vga1Magenta OBJECT-TYPE
        SYNTAX  INTEGER (0..100)
        ACCESS read-write
        STATUS  mandatory
        DESCRIPTION
                "Video Magenta"
        ::= { vga1 12 }
vga1Yellow OBJECT-TYPE
        SYNTAX  INTEGER (0..100)
        ACCESS read-write
        STATUS  mandatory
        DESCRIPTION
                "Video Yellow"
        ::= { vga1 13 }


hdmi2 OBJECT IDENTIFIER 
        ::= { video 4 }
hdmi2DisplayMode OBJECT-TYPE
        SYNTAX  INTEGER {
                        brightRoom(1),
                        darkRoom(2),
                        sRGB(3),
                        user(4),
                        smartPresentation(5)  }
        ACCESS read-write
        STATUS  mandatory
        DESCRIPTION
                "Video Display Mode"
        DEFVAL { smartPresentation }
        ::= { hdmi2 1 }
hdmi2Brightness OBJECT-TYPE
        SYNTAX  INTEGER (0..100)
        ACCESS read-write
        STATUS  mandatory
        DESCRIPTION
                "Video Brightness."
        ::= { hdmi2 2 }
hdmi2Contrast OBJECT-TYPE
        SYNTAX  INTEGER (0..100)
        ACCESS read-write
        STATUS  mandatory
        DESCRIPTION
                "Video Contrast."
        ::= { hdmi2 3 }
hdmi2Whitepeaking OBJECT-TYPE
        SYNTAX  INTEGER (0..10)
        ACCESS read-write
        STATUS  mandatory
        DESCRIPTION
                "Video White Peaking"
        ::= { hdmi2 4 }
hdmi2Degamma OBJECT-TYPE
        SYNTAX  INTEGER (0..3)
        ACCESS read-write
        STATUS  mandatory
        DESCRIPTION
                "Video Degamma"
        ::= { hdmi2 5 }
hdmi2Red OBJECT-TYPE
        SYNTAX  INTEGER (0..100)
        ACCESS read-write
        STATUS  mandatory
        DESCRIPTION
                "Video Red"
        ::= { hdmi2 6 }
hdmi2Green OBJECT-TYPE
        SYNTAX  INTEGER (0..100)
        ACCESS read-write
        STATUS  mandatory
        DESCRIPTION
                "Video Green"
        ::= { hdmi2 7 }
hdmi2Blue OBJECT-TYPE
        SYNTAX  INTEGER (0..100)
        ACCESS read-write
        STATUS  mandatory
        DESCRIPTION
                "Video Blue"
        ::= { hdmi2 8 }
hdmi2Cyan OBJECT-TYPE
        SYNTAX  INTEGER (0..100)
        ACCESS read-write
        STATUS  mandatory
        DESCRIPTION
                "Video Cyan"
        ::= { hdmi2 9 }
hdmi2Magenta OBJECT-TYPE
        SYNTAX  INTEGER (0..100)
        ACCESS read-write
        STATUS  mandatory
        DESCRIPTION
                "Video Magenta"
        ::= { hdmi2 10 }
hdmi2Yellow OBJECT-TYPE
        SYNTAX  INTEGER (0..100)
        ACCESS read-write
        STATUS  mandatory
        DESCRIPTION
                "Video Yellow"
        ::= { hdmi2 11 }

hdmi3 OBJECT IDENTIFIER 
        ::= { video 5 }
hdmi3DisplayMode OBJECT-TYPE
        SYNTAX  INTEGER {
                        brightRoom(1),
                        darkRoom(2),
                        sRGB(3),
                        user(4),
                        smartPresentation(5)  }
        ACCESS read-write
        STATUS  mandatory
        DESCRIPTION
                "Video Display Mode"
        DEFVAL { smartPresentation }
        ::= { hdmi3 1 }
hdmi3Brightness OBJECT-TYPE
        SYNTAX  INTEGER (0..100)
        ACCESS read-write
        STATUS  mandatory
        DESCRIPTION
                "Video Brightness."
        ::= { hdmi3 2 }
hdmi3Contrast OBJECT-TYPE
        SYNTAX  INTEGER (0..100)
        ACCESS read-write
        STATUS  mandatory
        DESCRIPTION
                "Video Contrast."
        ::= { hdmi3 3 }
hdmi3Whitepeaking OBJECT-TYPE
        SYNTAX  INTEGER (0..10)
        ACCESS read-write
        STATUS  mandatory
        DESCRIPTION
                "Video White Peaking"
        ::= { hdmi3 4 }
hdmi3Degamma OBJECT-TYPE
        SYNTAX  INTEGER (0..3)
        ACCESS read-write
        STATUS  mandatory
        DESCRIPTION
                "Video Degamma"
        ::= { hdmi3 5 }
hdmi3Red OBJECT-TYPE
        SYNTAX  INTEGER (0..100)
        ACCESS read-write
        STATUS  mandatory
        DESCRIPTION
                "Video Red"
        ::= { hdmi3 6 }
hdmi3Green OBJECT-TYPE
        SYNTAX  INTEGER (0..100)
        ACCESS read-write
        STATUS  mandatory
        DESCRIPTION
                "Video Green"
        ::= { hdmi3 7 }
hdmi3Blue OBJECT-TYPE
        SYNTAX  INTEGER (0..100)
        ACCESS read-write
        STATUS  mandatory
        DESCRIPTION
                "Video Blue"
        ::= { hdmi3 8 }
hdmi3Cyan OBJECT-TYPE
        SYNTAX  INTEGER (0..100)
        ACCESS read-write
        STATUS  mandatory
        DESCRIPTION
                "Video Cyan"
        ::= { hdmi3 9 }
hdmi3Magenta OBJECT-TYPE
        SYNTAX  INTEGER (0..100)
        ACCESS read-write
        STATUS  mandatory
        DESCRIPTION
                "Video Magenta"
        ::= { hdmi3 10 }
hdmi3Yellow OBJECT-TYPE
        SYNTAX  INTEGER (0..100)
        ACCESS read-write
        STATUS  mandatory
        DESCRIPTION
                "Video Yellow"
        ::= { hdmi3 11 }

vga2 OBJECT IDENTIFIER 
        ::= { video 6 }
vga2DisplayMode OBJECT-TYPE
        SYNTAX  INTEGER {
                        brightRoom(1),
                        darkRoom(2),
                        sRGB(3),
                        user(4),
                        smartPresentation(5) }
        ACCESS read-write
        STATUS  mandatory
        DESCRIPTION
                "Video Display Mode"
        DEFVAL { smartPresentation }
        ::= { vga2 1 }
vga2Brightness OBJECT-TYPE
        SYNTAX  INTEGER (0..100)
        ACCESS read-write
        STATUS  mandatory
        DESCRIPTION
                "Video Brightness."
        ::= { vga2 2 }
vga2Contrast OBJECT-TYPE
        SYNTAX  INTEGER (0..100)
        ACCESS read-write
        STATUS  mandatory
        DESCRIPTION
                "Video Contrast."
        ::= { vga2 3 }
vga2WhitePeaking OBJECT-TYPE
        SYNTAX  INTEGER (0..10)
        ACCESS read-write
        STATUS  mandatory
        DESCRIPTION
                "Video White Peaking"
        ::= { vga2 4 }
vga2Degamma OBJECT-TYPE
        SYNTAX  INTEGER (0..3)
        ACCESS read-write
        STATUS  mandatory
        DESCRIPTION
                "Video Degamma"
        ::= { vga2 5 }
vga2Red OBJECT-TYPE
        SYNTAX  INTEGER (0..100)
        ACCESS read-write
        STATUS  mandatory
        DESCRIPTION
                "Video Red"
        ::= { vga2 6 }
vga2Green OBJECT-TYPE
        SYNTAX  INTEGER (0..100)
        ACCESS read-write
        STATUS  mandatory
        DESCRIPTION
                "Video Green"
        ::= { vga2 7 }
vga2Blue OBJECT-TYPE
        SYNTAX  INTEGER (0..100)
        ACCESS read-write
        STATUS  mandatory
        DESCRIPTION
                "Video Blue"
        ::= { vga2 8 }
vga2Cyan OBJECT-TYPE
        SYNTAX  INTEGER (0..100)
        ACCESS read-write
        STATUS  mandatory
        DESCRIPTION
                "Video Cyan"
        ::= { vga2 9 }
vga2Magenta OBJECT-TYPE
        SYNTAX  INTEGER (0..100)
        ACCESS read-write
        STATUS  mandatory
        DESCRIPTION
                "Video Magenta"
        ::= { vga2 10 }
vga2Yellow OBJECT-TYPE
        SYNTAX  INTEGER (0..100)
        ACCESS read-write
        STATUS  mandatory
        DESCRIPTION
                "Video Yellow"
        ::= { vga2 11 }

composite1 OBJECT IDENTIFIER 
        ::= { video 7 }
composite1DisplayMode OBJECT-TYPE
        SYNTAX  INTEGER {
                        brightRoom(1),
                        darkRoom(2),
                        sRGB(3),
                        user(4),
                        smartPresentation(5)  }
        ACCESS read-write
        STATUS  mandatory
        DESCRIPTION
                "Video Display Mode"
        DEFVAL { smartPresentation }
        ::= { composite1 1 }
composite1Brightness OBJECT-TYPE
        SYNTAX  INTEGER (0..100)
        ACCESS read-write
        STATUS  mandatory
        DESCRIPTION
                "Video Brightness."
        ::= { composite1 2 }
composite1Contrast OBJECT-TYPE
        SYNTAX  INTEGER (0..100)
        ACCESS read-write
        STATUS  mandatory
        DESCRIPTION
                "Video Contrast."
        ::= { composite1 3 }
composite1Whitepeaking OBJECT-TYPE
        SYNTAX  INTEGER (0..10)
        ACCESS read-write
        STATUS  mandatory
        DESCRIPTION
                "Video White Peaking"
        ::= { composite1 4 }
composite1Degamma OBJECT-TYPE
        SYNTAX  INTEGER (0..3)
        ACCESS read-write
        STATUS  mandatory
        DESCRIPTION
                "Video Degamma"
        ::= { composite1 5 }
composite1Red OBJECT-TYPE
        SYNTAX  INTEGER (0..100)
        ACCESS read-write
        STATUS  mandatory
        DESCRIPTION
                "Video Red"
        ::= { composite1 6 }
composite1Green OBJECT-TYPE
        SYNTAX  INTEGER (0..100)
        ACCESS read-write
        STATUS  mandatory
        DESCRIPTION
                "Video Green"
        ::= { composite1 7 }
composite1Blue OBJECT-TYPE
        SYNTAX  INTEGER (0..100)
        ACCESS read-write
        STATUS  mandatory
        DESCRIPTION
                "Video Blue"
        ::= { composite1 8 }
composite1Cyan OBJECT-TYPE
        SYNTAX  INTEGER (0..100)
        ACCESS read-write
        STATUS  mandatory
        DESCRIPTION
                "Video Cyan"
        ::= { composite1 9 }
composite1Magenta OBJECT-TYPE
        SYNTAX  INTEGER (0..100)
        ACCESS read-write
        STATUS  mandatory
        DESCRIPTION
                "Video Magenta"
        ::= { composite1 10 }
composite1Yellow OBJECT-TYPE
        SYNTAX  INTEGER (0..100)
        ACCESS read-write
        STATUS  mandatory
        DESCRIPTION
                "Video Yellow"
        ::= { composite1 11 }

hdmi4 OBJECT IDENTIFIER 
        ::= { video 8 }
hdmi4DisplayMode OBJECT-TYPE
        SYNTAX  INTEGER {
                        brightRoom(1),
                        darkRoom(2),
                        sRGB(3),
                        user(4),
                        smartPresentation(5)  }
        ACCESS read-write
        STATUS  mandatory
        DESCRIPTION
                "Video Display Mode"
        DEFVAL { smartPresentation }
        ::= { hdmi4 1 }
hdmi4Brightness OBJECT-TYPE
        SYNTAX  INTEGER (0..100)
        ACCESS read-write
        STATUS  mandatory
        DESCRIPTION
                "Video Brightness."
        ::= { hdmi4 2 }
hdmi4Contrast OBJECT-TYPE
        SYNTAX  INTEGER (0..100)
        ACCESS read-write
        STATUS  mandatory
        DESCRIPTION
                "Video Contrast."
        ::= { hdmi4 3 }
hdmi4Whitepeaking OBJECT-TYPE
        SYNTAX  INTEGER (0..10)
        ACCESS read-write
        STATUS  mandatory
        DESCRIPTION
                "Video White Peaking"
        ::= { hdmi4 4 }
hdmi4Degamma OBJECT-TYPE
        SYNTAX  INTEGER (0..3)
        ACCESS read-write
        STATUS  mandatory
        DESCRIPTION
                "Video Degamma"
        ::= { hdmi4 5 }
hdmi4Red OBJECT-TYPE
        SYNTAX  INTEGER (0..100)
        ACCESS read-write
        STATUS  mandatory
        DESCRIPTION
                "Video Red"
        ::= { hdmi4 6 }
hdmi4Green OBJECT-TYPE
        SYNTAX  INTEGER (0..100)
        ACCESS read-write
        STATUS  mandatory
        DESCRIPTION
                "Video Green"
        ::= { hdmi4 7 }
hdmi4Blue OBJECT-TYPE
        SYNTAX  INTEGER (0..100)
        ACCESS read-write
        STATUS  mandatory
        DESCRIPTION
                "Video Blue"
        ::= { hdmi4 8 }
hdmi4Cyan OBJECT-TYPE
        SYNTAX  INTEGER (0..100)
        ACCESS read-write
        STATUS  mandatory
        DESCRIPTION
                "Video Cyan"
        ::= { hdmi4 9 }
hdmi4Magenta OBJECT-TYPE
        SYNTAX  INTEGER (0..100)
        ACCESS read-write
        STATUS  mandatory
        DESCRIPTION
                "Video Magenta"
        ::= { hdmi4 10 }
hdmi4Yellow OBJECT-TYPE
        SYNTAX  INTEGER (0..100)
        ACCESS read-write
        STATUS  mandatory
        DESCRIPTION
                "Video Yellow"
        ::= { hdmi4 11 }

hdmi5 OBJECT IDENTIFIER 
        ::= { video 9 }
hdmi5DisplayMode OBJECT-TYPE
        SYNTAX  INTEGER {
                        brightRoom(1),
                        darkRoom(2),
                        sRGB(3),
                        user(4),
                        smartPresentation(5)  }
        ACCESS read-write
        STATUS  mandatory
        DESCRIPTION
                "Video Display Mode"
        DEFVAL { smartPresentation }
        ::= { hdmi5 1 }
hdmi5Brightness OBJECT-TYPE
        SYNTAX  INTEGER (0..100)
        ACCESS read-write
        STATUS  mandatory
        DESCRIPTION
                "Video Brightness."
        ::= { hdmi5 2 }
hdmi5Contrast OBJECT-TYPE
        SYNTAX  INTEGER (0..100)
        ACCESS read-write
        STATUS  mandatory
        DESCRIPTION
                "Video Contrast."
        ::= { hdmi5 3 }
hdmi5Whitepeaking OBJECT-TYPE
        SYNTAX  INTEGER (0..10)
        ACCESS read-write
        STATUS  mandatory
        DESCRIPTION
                "Video White Peaking"
        ::= { hdmi5 4 }
hdmi5Degamma OBJECT-TYPE
        SYNTAX  INTEGER (0..3)
        ACCESS read-write
        STATUS  mandatory
        DESCRIPTION
                "Video Degamma"
        ::= { hdmi5 5 }
hdmi5Red OBJECT-TYPE
        SYNTAX  INTEGER (0..100)
        ACCESS read-write
        STATUS  mandatory
        DESCRIPTION
                "Video Red"
        ::= { hdmi5 6 }
hdmi5Green OBJECT-TYPE
        SYNTAX  INTEGER (0..100)
        ACCESS read-write
        STATUS  mandatory
        DESCRIPTION
                "Video Green"
        ::= { hdmi5 7 }
hdmi5Blue OBJECT-TYPE
        SYNTAX  INTEGER (0..100)
        ACCESS read-write
        STATUS  mandatory
        DESCRIPTION
                "Video Blue"
        ::= { hdmi5 8 }
hdmi5Cyan OBJECT-TYPE
        SYNTAX  INTEGER (0..100)
        ACCESS read-write
        STATUS  mandatory
        DESCRIPTION
                "Video Cyan"
        ::= { hdmi5 9 }
hdmi5Magenta OBJECT-TYPE
        SYNTAX  INTEGER (0..100)
        ACCESS read-write
        STATUS  mandatory
        DESCRIPTION
                "Video Magenta"
        ::= { hdmi5 10 }
hdmi5Yellow OBJECT-TYPE
        SYNTAX  INTEGER (0..100)
        ACCESS read-write
        STATUS  mandatory
        DESCRIPTION
                "Video Yellow"
        ::= { hdmi5 11 }


vga3 OBJECT IDENTIFIER 
        ::= { video 10 }
vga3DisplayMode OBJECT-TYPE
        SYNTAX  INTEGER {
                        brightRoom(1),
                        darkRoom(2),
                        sRGB(3),
                        user(4),
                        smartPresentation(5) }
        ACCESS read-write
        STATUS  mandatory
        DESCRIPTION
                "Video Display Mode"
        DEFVAL { smartPresentation }
        ::= { vga3 1 }
vga3Brightness OBJECT-TYPE
        SYNTAX  INTEGER (0..100)
        ACCESS read-write
        STATUS  mandatory
        DESCRIPTION
                "Video Brightness."
        ::= { vga3 2 }
vga3Contrast OBJECT-TYPE
        SYNTAX  INTEGER (0..100)
        ACCESS read-write
        STATUS  mandatory
        DESCRIPTION
                "Video Contrast."
        ::= { vga3 3 }
vga3WhitePeaking OBJECT-TYPE
        SYNTAX  INTEGER (0..10)
        ACCESS read-write
        STATUS  mandatory
        DESCRIPTION
                "Video White Peaking"
        ::= { vga3 4 }
vga3Degamma OBJECT-TYPE
        SYNTAX  INTEGER (0..3)
        ACCESS read-write
        STATUS  mandatory
        DESCRIPTION
                "Video Degamma"
        ::= { vga3 5 }
vga3Red OBJECT-TYPE
        SYNTAX  INTEGER (0..100)
        ACCESS read-write
        STATUS  mandatory
        DESCRIPTION
                "Video Red"
        ::= { vga3 6 }
vga3Green OBJECT-TYPE
        SYNTAX  INTEGER (0..100)
        ACCESS read-write
        STATUS  mandatory
        DESCRIPTION
                "Video Green"
        ::= { vga3 7 }
vga3Blue OBJECT-TYPE
        SYNTAX  INTEGER (0..100)
        ACCESS read-write
        STATUS  mandatory
        DESCRIPTION
                "Video Blue"
        ::= { vga3 8 }
vga3Cyan OBJECT-TYPE
        SYNTAX  INTEGER (0..100)
        ACCESS read-write
        STATUS  mandatory
        DESCRIPTION
                "Video Cyan"
        ::= { vga3 9 }
vga3Magenta OBJECT-TYPE
        SYNTAX  INTEGER (0..100)
        ACCESS read-write
        STATUS  mandatory
        DESCRIPTION
                "Video Magenta"
        ::= { vga3 10 }
vga3Yellow OBJECT-TYPE
        SYNTAX  INTEGER (0..100)
        ACCESS read-write
        STATUS  mandatory
        DESCRIPTION
                "Video Yellow"
        ::= { vga3 11 }

composite2 OBJECT IDENTIFIER 
        ::= { video 11 }
composite2DisplayMode OBJECT-TYPE
        SYNTAX  INTEGER {
                        brightRoom(1),
                        darkRoom(2),
                        sRGB(3),
                        user(4),
                        smartPresentation(5)  }
        ACCESS read-write
        STATUS  mandatory
        DESCRIPTION
                "Video Display Mode"
        DEFVAL { smartPresentation }
        ::= { composite2 1 }
composite2Brightness OBJECT-TYPE
        SYNTAX  INTEGER (0..100)
        ACCESS read-write
        STATUS  mandatory
        DESCRIPTION
                "Video Brightness."
        ::= { composite2 2 }
composite2Contrast OBJECT-TYPE
        SYNTAX  INTEGER (0..100)
        ACCESS read-write
        STATUS  mandatory
        DESCRIPTION
                "Video Contrast."
        ::= { composite2 3 }
composite2Whitepeaking OBJECT-TYPE
        SYNTAX  INTEGER (0..10)
        ACCESS read-write
        STATUS  mandatory
        DESCRIPTION
                "Video White Peaking"
        ::= { composite2 4 }
composite2Degamma OBJECT-TYPE
        SYNTAX  INTEGER (0..3)
        ACCESS read-write
        STATUS  mandatory
        DESCRIPTION
                "Video Degamma"
        ::= { composite2 5 }
composite2Red OBJECT-TYPE
        SYNTAX  INTEGER (0..100)
        ACCESS read-write
        STATUS  mandatory
        DESCRIPTION
                "Video Red"
        ::= { composite2 6 }
composite2Green OBJECT-TYPE
        SYNTAX  INTEGER (0..100)
        ACCESS read-write
        STATUS  mandatory
        DESCRIPTION
                "Video Green"
        ::= { composite2 7 }
composite2Blue OBJECT-TYPE
        SYNTAX  INTEGER (0..100)
        ACCESS read-write
        STATUS  mandatory
        DESCRIPTION
                "Video Blue"
        ::= { composite2 8 }
composite2Cyan OBJECT-TYPE
        SYNTAX  INTEGER (0..100)
        ACCESS read-write
        STATUS  mandatory
        DESCRIPTION
                "Video Cyan"
        ::= { composite2 9 }
composite2Magenta OBJECT-TYPE
        SYNTAX  INTEGER (0..100)
        ACCESS read-write
        STATUS  mandatory
        DESCRIPTION
                "Video Magenta"
        ::= { composite2 10 }
composite2Yellow OBJECT-TYPE
        SYNTAX  INTEGER (0..100)
        ACCESS read-write
        STATUS  mandatory
        DESCRIPTION
                "Video Yellow"
        ::= { composite2 11 }

currentInput OBJECT IDENTIFIER 
        ::= { video 12 }
displayMode OBJECT-TYPE
        SYNTAX  INTEGER {
                        brightRoom(1),
                        darkRoom(2),
                        sRGB(3),
                        user(4),
                        smartPresentation(5)  }
        ACCESS read-write
        STATUS  mandatory
        DESCRIPTION
                "Video Display Mode"
        DEFVAL { smartPresentation }
        ::= { currentInput 1 }
brightness OBJECT-TYPE
        SYNTAX  INTEGER (0..100)
        ACCESS read-write
        STATUS  mandatory
        DESCRIPTION
                "Video Brightness."
        ::= { currentInput 2 }
contrast OBJECT-TYPE
        SYNTAX  INTEGER (0..100)
        ACCESS read-write
        STATUS  mandatory
        DESCRIPTION
                "Video Contrast."
        ::= { currentInput 3 }
frequency OBJECT-TYPE
        SYNTAX  INTEGER (-5..5)
        ACCESS read-write
        STATUS  mandatory
        DESCRIPTION
                "Video Frequency"
        ::= { currentInput 4 }
tracking OBJECT-TYPE
        SYNTAX  INTEGER (0..63)
        ACCESS read-write
        STATUS  mandatory
        DESCRIPTION
                "Video Tracking"
        ::= { currentInput 5 }
whitepeaking OBJECT-TYPE
        SYNTAX  INTEGER (0..10)
        ACCESS read-write
        STATUS  mandatory
        DESCRIPTION
                "Video White Peaking"
        ::= { currentInput 6 }
degamma OBJECT-TYPE
        SYNTAX  INTEGER (0..3)
        ACCESS read-write
        STATUS  mandatory
        DESCRIPTION
                "Video Degamma"
        ::= { currentInput 7 }
red OBJECT-TYPE
        SYNTAX  INTEGER (0..100)
        ACCESS read-write
        STATUS  mandatory
        DESCRIPTION
                "Video Red"
        ::= { currentInput 8 }
green OBJECT-TYPE
        SYNTAX  INTEGER (0..100)
        ACCESS read-write
        STATUS  mandatory
        DESCRIPTION
                "Video Green"
        ::= { currentInput 9 }
blue OBJECT-TYPE
        SYNTAX  INTEGER (0..100)
        ACCESS read-write
        STATUS  mandatory
        DESCRIPTION
                "Video Blue"
        ::= { currentInput 10 }
cyan OBJECT-TYPE
        SYNTAX  INTEGER (0..100)
        ACCESS read-write
        STATUS  mandatory
        DESCRIPTION
                "Video Cyan"
        ::= { currentInput 11 }
magenta OBJECT-TYPE
        SYNTAX  INTEGER (0..100)
        ACCESS read-write
        STATUS  mandatory
        DESCRIPTION
                "Video Magenta"
        ::= { currentInput 12 }
yellow OBJECT-TYPE
        SYNTAX  INTEGER (0..100)
        ACCESS read-write
        STATUS  mandatory
        DESCRIPTION
                "Video Yellow"
        ::= { currentInput 13 }

aspectRatio OBJECT-TYPE
        SYNTAX  INTEGER {
                        fill(1),
                        match(2),
                        widescreen169(3) }
        ACCESS read-write
        STATUS  mandatory
        DESCRIPTION
                "Video Aspect Ratio"
        DEFVAL { fill }
        ::= { video 13 }

zoom OBJECT-TYPE
        SYNTAX  INTEGER (0..30)
        ACCESS read-write
        STATUS  mandatory
        DESCRIPTION
                "Video Zoom"
        ::= { video 14 }

hposition OBJECT-TYPE
        SYNTAX  INTEGER
        ACCESS read-write
        STATUS  mandatory
        DESCRIPTION
                "Horizontal Position"
        ::= { video 15 }

vposition OBJECT-TYPE
        SYNTAX  INTEGER
        ACCESS read-write
        STATUS  mandatory
        DESCRIPTION
                "Vertical Position"
        ::= { video 16 }


videoMute OBJECT-TYPE
        SYNTAX  INTEGER {
                        videomuteoff(1),
                        videomuteon(2)  }
        ACCESS read-write
        STATUS  mandatory
        DESCRIPTION
                "Video Mute enable/disable"
        DEFVAL { videomuteoff }
        ::= { video 17 }

videoFreeze OBJECT-TYPE
        SYNTAX  INTEGER {
                        unfreeze(1),
                        freeze(2)  }
        ACCESS read-write
        STATUS  mandatory
        DESCRIPTION
                "Freeze / Unfreeze the Video Display"
        DEFVAL { unfreeze }
        ::= { video 18 }


videoUsb1Source OBJECT-TYPE
        SYNTAX  INTEGER {
                        hdmi1(1),
                        hdmi2(2),
                        vga(3),
                        disabled(4)
                         }
        ACCESS read-write
        STATUS  mandatory
        DESCRIPTION
                "Causes USB1 to be active when the input is selected.
                1: HDMI 1
                2: HDMI 2
                3: VGA
                4: Disabled

                If usb1source and usb2source are the same, usb1 is used."
        ::= { video 19 }

videoUsb2Source OBJECT-TYPE
        SYNTAX  INTEGER {
                        hdmi1(1),
                        hdmi2(2),
                        vga(3),
                        disabled(4)
                         }
        ACCESS read-write
        STATUS  mandatory
        DESCRIPTION
                "Causes USB2 to be active when the input is selected.
                1: HDMI 1
                2: HDMI 2
                3: VGA
                4: Disabled"
        ::= { video 20 }


audio OBJECT IDENTIFIER 
        ::= { ux80 3 }

audioVolume OBJECT-TYPE
        SYNTAX  INTEGER (0..40)
        ACCESS read-write
        STATUS  mandatory
        DESCRIPTION
                "Audio volume.
                0 is the minimum and 40 is the maximum."
        ::= { audio 1 }


audioMute OBJECT-TYPE
        SYNTAX  INTEGER {
                        muteoff(1),
                        muteon(2) }
        ACCESS read-write
        STATUS  mandatory
        DESCRIPTION
                "To mute audio set to 2.
                To un-mute audio set to 1."
        DEFVAL { muteoff }
        ::= { audio 2 }

audioVolumeControl OBJECT-TYPE
        SYNTAX  INTEGER {
                        controloff(1),
                        controlon(2) }
        ACCESS read-write
        STATUS  mandatory
        DESCRIPTION
                "To control the audio, set to 2.
                To not control the audio, set to 1."
        DEFVAL { controlon }
        ::= { audio 3 }

audioSysOutputSw OBJECT-TYPE
        SYNTAX  INTEGER {
                        lineoutandspeaker(1),
						lineout(2),
                        speaker(3) }
        ACCESS read-write
        STATUS  mandatory
        DESCRIPTION
                "Audio System Output Switch for WXGA"
        DEFVAL { lineout }
        ::= { audio 4 }

network OBJECT IDENTIFIER 
        ::= { ux80 4 }

netStatus OBJECT-TYPE
        SYNTAX  INTEGER {
                        connected(1),
                        disconnected(2) }
        ACCESS read-only
        STATUS  mandatory
        DESCRIPTION
                "Status of the network.  Currently it will always be connected if this can be read."
        DEFVAL { connected }
        ::= { network 1 }

netDHCP OBJECT-TYPE
        SYNTAX  INTEGER {
                        disable(1),
                        enable(2) }
        ACCESS read-write
        STATUS  mandatory
        DESCRIPTION
                "To enable DHCP set to 2.
                To disable DHCP set to 1.
                    Note: you must reboot for
                    static setings to take effect."
        DEFVAL { enable }
        ::= { network 2 }

netIPAddress OBJECT-TYPE
        SYNTAX  IpAddress
        ACCESS read-write
        STATUS  mandatory
        DESCRIPTION
                "IP Address of the device."
        ::= { network 3 }

netSubnetMask OBJECT-TYPE
        SYNTAX  IpAddress
        ACCESS read-write
        STATUS  mandatory
        DESCRIPTION
                "IP Configuration Netmask."
        ::= { network 4 }

netGateway OBJECT-TYPE
        SYNTAX  IpAddress
        ACCESS read-write
        STATUS  mandatory
        DESCRIPTION
                "Gateway configuration."
        ::= { network 5 }

netPrimaryDNS OBJECT-TYPE
        SYNTAX  IpAddress
        ACCESS read-write
        STATUS  mandatory
        DESCRIPTION
                "Primary DNS Server configuration."
        ::= { network 6 }

netMacAddress OBJECT-TYPE
        SYNTAX  OCTET STRING
        ACCESS read-only
        STATUS  mandatory
        DESCRIPTION
                "MAC Address."
        ::= { network 7 }

config OBJECT IDENTIFIER 
        ::= { ux80 5 }

configLanguage OBJECT-TYPE
        SYNTAX  INTEGER {
                        english(1),
                        spanish(2),
                        french(3),
                        brazilianPortuguese(4),
                        japanese(5),
                        simplifiedChinese(6),
                        traditionalChinese(7),
                        korean(8),
                        german(9),
                        italian(10),
                        dutch(11),
                        danish(12),
                        finnish(13),
                        greek(14),
                        norwegian(15),
                        polish(16),
                        czech(17),
                        swedish(18),
                        iberianPortuguese(19),
                        russian(20)
                        }
        ACCESS read-write
        STATUS  mandatory
        DESCRIPTION
                "Set to the following to switch between 
                different languages:
                 1: English
                 2: Spanish
                 3: French
                 4: Brazilian Portuguese
                 5: Japanese
                 6: Simplified Chinese
                 7: Traditional Chinese
                 8: Korean
                 9: German
                10: Italian
                11: Dutch
                12: Danish
                13: Finnish
                14: Greek
                15: Norwegian
                16: Polish
                17: Czech
                18: Swedish
                19: Iberian Portuguese
                20: Russian"
        DEFVAL { english }
        ::= { config 1 }

configReset OBJECT-TYPE
        SYNTAX  INTEGER { reset(1) }
        ACCESS read-write
        STATUS  mandatory
        DESCRIPTION
                "Set to 1 will cause the projector to reset."
        ::= { config 2 }

sysInfo OBJECT IDENTIFIER 
        ::= { ux80 6 }

sysInfoInputFormat OBJECT-TYPE
        SYNTAX  OCTET STRING
        ACCESS read-only
        STATUS  mandatory
        DESCRIPTION
                "Current Resolution the system is receiving and outputting. 
                 If no signal is detected, `no signal` should be returned."
        ::= { sysInfo 1 } 

sysInfoFWVerDDP OBJECT-TYPE
        SYNTAX  OCTET STRING
        ACCESS read-only
        STATUS  mandatory
        DESCRIPTION
                "DDP Firmware Version"
        ::= { sysInfo 2 }


sysInfoLampHour OBJECT-TYPE
        SYNTAX  INTEGER
        ACCESS read-write
        STATUS  mandatory
        DESCRIPTION
                "Attached Projector Lamp Hours.  If 
                written to a value of zero, the value is
                reset.  All other writes are ignored.
                "
        ::= { sysInfo 3 }

sysAutoSignal OBJECT-TYPE
        SYNTAX  INTEGER {
                         on(1),
                         off(2)
                        }
        ACCESS read-write
        STATUS  mandatory
        DESCRIPTION
                "Turn on/off autosignal."
        ::= { sysInfo 4 }

sysLampReminder OBJECT-TYPE
        SYNTAX  INTEGER { 
                        on(1),
                        off(2)
                        }
        ACCESS read-write
        STATUS  mandatory
        DESCRIPTION
                "Turn on/off lamp reminder."
        ::= { sysInfo 5 }

sysHighBrightness OBJECT-TYPE
        SYNTAX  INTEGER { 
                        on(1),
                        off(2)
                        }
        ACCESS read-write
        STATUS  mandatory
        DESCRIPTION
                "Turn on/off high brightness."
        ::= { sysInfo 6 }

sysAutoPowerOff OBJECT-TYPE
        SYNTAX  INTEGER (0..240)
        ACCESS read-write
        STATUS  mandatory
        DESCRIPTION
                "Turn on/off auto Power Off."
        ::= { sysInfo 7 }

sysProjectorID OBJECT-TYPE
        SYNTAX  INTEGER (0..99)
        ACCESS read-write
        STATUS  mandatory
        DESCRIPTION
                "Projector ID"
        ::= { sysInfo 8 }

sysStartupScreen OBJECT-TYPE
        SYNTAX  INTEGER { 
                        smart(1),
                        usercapture(2),
                        preview(3)
                        }
        ACCESS read-write
        STATUS  mandatory
        DESCRIPTION
                "Startup Screen."
        ::= { sysInfo 10 }

sysGroupName OBJECT-TYPE
        SYNTAX  OCTET STRING
        ACCESS read-only
        STATUS  mandatory
        DESCRIPTION
                "Projector Group Name"
        ::= { sysInfo 11 }

sysProjectorName OBJECT-TYPE
        SYNTAX  OCTET STRING
        ACCESS read-only
        STATUS  mandatory
        DESCRIPTION
                "Projector Name."
        ::= { sysInfo 12 }

sysLocation OBJECT-TYPE
        SYNTAX  OCTET STRING
        ACCESS read-only
        STATUS  mandatory
        DESCRIPTION
                "Location"
        ::= { sysInfo 13 }

sysContact OBJECT-TYPE
        SYNTAX  OCTET STRING
        ACCESS read-only
        STATUS  mandatory
        DESCRIPTION
                "Contact"
        ::= { sysInfo 14 }

sysDisplayHour OBJECT-TYPE
        SYNTAX  INTEGER (0..20000)
        ACCESS read-only
        STATUS  mandatory
        DESCRIPTION
                "Display Hours."
        ::= { sysInfo 15 }

sysModelNumber OBJECT-TYPE
        SYNTAX  OCTET STRING
        ACCESS read-only
        STATUS  mandatory
        DESCRIPTION
                "Model Number of the projector"
        ::= { sysInfo 16 }

sysInfoFWVerMpu OBJECT-TYPE
        SYNTAX  OCTET STRING
        ACCESS read-only
        STATUS  mandatory
        DESCRIPTION
                "MPU Firmware Version"
        ::= { sysInfo 17 }

sysInfoFWVerNet OBJECT-TYPE
        SYNTAX  OCTET STRING
        ACCESS read-only
        STATUS  mandatory
        DESCRIPTION
                "NET Firmware Version"
        ::= { sysInfo 18 }

sysInfoSerialNumber OBJECT-TYPE
        SYNTAX  OCTET STRING
        ACCESS read-only
        STATUS  mandatory
        DESCRIPTION
                "Projector Serial Number"
        ::= { sysInfo 19 }

sysInfoFWVerECP OBJECT-TYPE
        SYNTAX  OCTET STRING
        ACCESS read-only
        STATUS  mandatory
        DESCRIPTION
                "ECP Firmware Version"
        ::= { sysInfo 20 }

sysInfoInputDetected OBJECT-TYPE
        SYNTAX  INTEGER {
                         true(1),
                         false(2)
                        }
        ACCESS read-only
        STATUS  mandatory
        DESCRIPTION
                "Has a signal been detected or not."
        ::= { sysInfo 21 }

serviceMenu OBJECT IDENTIFIER 
        ::= { ux80 7 }

serviceFailureLog OBJECT-TYPE
        SYNTAX  INTEGER { 
                        normal(1),
                        overtemp(2),
                        fanlock(3),
			fancw(4),
			fanblower(5),
			fansystem(6),
                        lamperror(7),
                        colorwheelbreak(8),
                        lampoverheat(9),
                        lampdriver(10),
			lampoverhours(11),
			lampigniteerror(12)
                        }
        ACCESS read-only
        STATUS  mandatory
        DESCRIPTION
                "Failure log"
        ::= { serviceMenu 1 }

serviceRestoreDefaults OBJECT-TYPE
        SYNTAX  INTEGER { restore(1) }
        ACCESS read-write
        STATUS  mandatory
        DESCRIPTION
                "Set to 1 to restore factory defaults.
                NOTE: UX80 will reboot immediately after."
        ::= { serviceMenu 2 }

serviceHighSpeedFan OBJECT-TYPE
        SYNTAX  INTEGER { 
                        high(1),
                        normal(2)
                        }
        ACCESS read-write
        STATUS  mandatory
        DESCRIPTION
                "Fan Speed"
        ::= { serviceMenu 3 }

serviceProjectionMode OBJECT-TYPE
        SYNTAX  INTEGER { 
                        front(1),
                        ceiling(2),
                        rear(3),
                        rearceiling(4)
                        }
        ACCESS read-write
        STATUS  mandatory
        DESCRIPTION
                "Projection Mode."
        ::= { serviceMenu 4 }

servicePowerOverride OBJECT-TYPE
        SYNTAX  INTEGER { 
                        on(1),
                        off(2)
                        }
        ACCESS read-write
        STATUS  mandatory
        DESCRIPTION
                "Indicates if the power override is on or off"
        ::= { serviceMenu 5 }

threeD OBJECT IDENTIFIER 
        ::= { ux80 8 }

threeDEnable OBJECT-TYPE
        SYNTAX  INTEGER {
                         on(1),
                         off(2)
                        }
        ACCESS read-write
        STATUS  mandatory
        DESCRIPTION
                "3D mode on/off"
        ::= { threeD 1 }

threeDInvert OBJECT-TYPE
        SYNTAX  INTEGER {
                         leftRight(1),
                         rightLeft(2)
                        }
        ACCESS read-write
        STATUS  mandatory
        DESCRIPTION
                "3D invert mode.  Left then right / Right before left"
        ::= { threeD 2 }

threeDFormat OBJECT-TYPE
        SYNTAX  INTEGER {
                         interleaved(1),
                         overunder(2),
                         fieldsequential(3),
                         framesequential(4),
                         topbottom(5),
                         framepacking(6),
                         sidebyside(7),
                         sidebysidefull(8)
                        }
        ACCESS read-write
        STATUS  mandatory
        DESCRIPTION
                "3D format mode"
        ::= { threeD 3 }

emergencyAlert OBJECT IDENTIFIER 
        ::= { ux80 9 }

emergencyDisplay OBJECT-TYPE
        SYNTAX  INTEGER {
                         on(1),
                         off(2)
                        }
        ACCESS read-write
        STATUS  mandatory
        DESCRIPTION
                "Display the Emergency Alert message"
        ::= { emergencyAlert 1 }

emergencyAlertMsg OBJECT-TYPE
        SYNTAX  OCTET STRING
        ACCESS read-write
        STATUS  mandatory
        DESCRIPTION
                "Define the emergency message"
        ::= { emergencyAlert 2 }

failureLogTrap TRAP-TYPE
        ENTERPRISE  smartTechULC
        VARIABLES   { serviceFailureLog }
        DESCRIPTION
                    "A failure has occured.  Send out the notification!"
        ::= 1

powerStateChange TRAP-TYPE
        ENTERPRISE  smartTechULC
        VARIABLES   { powerState }
        DESCRIPTION
                    "Power state on the projector has changed."
        ::= 2

END
